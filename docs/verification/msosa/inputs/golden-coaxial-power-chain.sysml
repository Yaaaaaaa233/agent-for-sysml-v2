// Generated by sysml-modeling-agent - schema sysml-ir/v1.
// Source of truth is the IR JSON; regenerate with generate_sysml. Do not edit by hand.
package CoaxialOctoRotor {
    private import ScalarValues::*;
    private import SI::*;

    // ---- PartDefinition ----
    // id: PART-BATTERY-PACK
    // description: 动力锂电池包，为整机提供能量。
    part def BatteryPack {
        // id: ATTR-BATTERY-CAPACITY
        // description: 电池包标称容量 E_batt。
        attribute batteryCapacityWh : Real = 1200.0 [W*h];
        // id: ATTR-USABLE-FRACTION
        // description: 可安全放出的容量占比（扣除降落裕度与低压保护），无量纲。
        attribute usableEnergyFraction : Real = 0.8;
    }
    // id: PART-ESC
    // description: 电子调速器，把电池直流电按转速指令调制后驱动电机。
    part def ElectronicSpeedController {
        // id: ATTR-ESC-EFFICIENCY
        // description: 电调效率 eta_esc，无量纲。
        attribute escEfficiency : Real = 0.95;
    }
    // id: PART-MOTOR
    // description: 无刷直流电机，把电功率转换为轴功率。
    part def BrushlessMotor {
        // id: ATTR-MOTOR-EFFICIENCY
        // description: 电机效率 eta_motor，无量纲。
        attribute motorEfficiency : Real = 0.85;
    }
    // id: PART-POWER-CHAIN
    // description: 功率链：电池 → 电调 → 电机 → 桨；上下桨各占一条并联支路。
    part def PowerChain {
        // id: PART-USAGE-BATTERY
        // description: 功率链电源端。
        part batteryPack : BatteryPack[1] {
            // 追溯关系 (relations):
            //   PART-USAGE-BATTERY --connects--> PART-USAGE-ESC  (电池直流母线馈入八路电调)
        }
        // id: PART-USAGE-ESC
        // description: 八路电调，每副桨一路。
        part escUnit : ElectronicSpeedController[8] {
            // 追溯关系 (relations):
            //   PART-USAGE-ESC --connects--> PART-USAGE-MOTOR-UPPER  (电调按转速指令驱动上桨电机)
            //   PART-USAGE-ESC --connects--> PART-USAGE-MOTOR-LOWER  (同一路电调的另一支路驱动下桨电机)
        }
        // id: PART-USAGE-MOTOR-LOWER
        // description: 四根机臂上的下桨电机。
        part lowerMotor : BrushlessMotor[4] {
            // 追溯关系 (relations):
            //   PART-USAGE-MOTOR-LOWER --connects--> PART-USAGE-PROP-LOWER  (下桨电机把轴功率传给下桨)
        }
        // id: PART-USAGE-MOTOR-UPPER
        // description: 四根机臂上的上桨电机。
        part upperMotor : BrushlessMotor[4] {
            // 追溯关系 (relations):
            //   PART-USAGE-MOTOR-UPPER --connects--> PART-USAGE-PROP-UPPER  (上桨电机把轴功率传给上桨)
        }
        // id: PART-USAGE-PROP-LOWER
        part lowerPropeller : LowerRotor[4];
        // id: PART-USAGE-PROP-UPPER
        part upperPropeller : UpperRotor[4];
        // id: ATTR-CRUISE-POWER
        // description: 巡航稳态整机电功率 P_cruise；由各环节效率链折算：P_cruise = P_shaft / (eta_esc * eta_motor * eta_prop)，其中 P_shaft 为上下桨轴功率之和。
        attribute cruisePowerW : Real = 240.0 [W];
        // id: ATTR-ENDURANCE
        // description: 续航换算：T = E_batt * usableEnergyFraction / P_cruise。代入 1200 Wh、0.8、240 W 得 T = 4.0 h，恰好满足 REQ-CRUISE-ENDURANCE 的下限。
        attribute enduranceHours : Real = 4.0 [h];
        // id: ATTR-PROP-EFFICIENCY
        // description: 共轴双桨的气动效率 eta_prop（含上下桨气动干涉损失与逆风漂移），无量纲。
        attribute propellerEfficiency : Real = 0.72;
        // id: CONSTRAINT-ENDURANCE-BUDGET
        // description: 续航换算约束：电池可用能量除以巡航功率得到续航时间。parameters 把公式里的符号绑定到 Attribute 元素；1200 Wh / 0.8 / 240 W / 4.0 h 均为占位示例值，非实测结论。
        constraint def EnduranceBudget {
            // expression: T = batteryCapacityWh * usableEnergyFraction / cruisePowerW
            // parameters: batteryCapacityWh, usableEnergyFraction, cruisePowerW, enduranceHours
        }
        // Connection CONN-BATTERY-ESC flowKind=electrical name=batteryToEsc description: 电池直流母线馈入八路电调。
        connect batteryPack to escUnit;
        // Connection CONN-UPPER-MOTOR-PROP flowKind=mechanical name=upperMotorToPropeller description: 上桨电机把轴功率传给上桨。
        connect upperMotor to upperPropeller;
    }
    // id: PART-PROP-LOWER
    // description: 共轴对的下桨，转速为下桨转速 n_lower。
    part def LowerRotor;
    // id: PART-PROP-UPPER
    // description: 共轴对的上桨，转速为上桨转速 n_upper。
    part def UpperRotor;
    // id: PART-STRUCT-SYSTEM
    // description: 共轴八旋翼整机系统（X8）：四根机臂，每臂上下两副桨共轴叠放。
    part def CoaxialOctoRotorSystem {
        // id: PART-USAGE-POWER-CHAIN
        // description: 整机中功率链的那一份实例。
        part powerChain : PowerChain[1];
        // id: ATTR-CRUISE-SPEED
        // description: 巡航平飞速度 v，在线寻优的两个决策量之一。
        attribute cruiseSpeed : Real = 15.0 [m/s];
        // id: ATTR-SPEED-RATIO
        // description: 上下桨转速比 eta = n_upper / n_lower，无量纲；在线寻优的另一个决策量。
        attribute speedRatioEta : Real = 1.0;
        // 追溯关系 (relations):
        //   PART-STRUCT-SYSTEM --decomposes--> PART-POWER-CHAIN  (整机在结构上分解为功率链等子系统)
    }

    // ---- PartUsage ----
    // id: PART-USAGE-SYSTEM
    // description: 本架共轴八旋翼的顶层实例（模型中唯一一份整机）。
    part x8System : CoaxialOctoRotorSystem[1] {
        // 追溯关系 (relations):
        //   PART-USAGE-SYSTEM --satisfiedBy--> REQ-MISSION-ENDURANCE  (整机实例承载任务级续航需求)
    }

    // ---- Requirement ----
    // id: REQ-CRUISE-ENDURANCE
    requirement def CruiseEndurance {
        doc /* 巡航时间不低于 4 小时 */
        doc /* 验收判据: 在巡航速度 v 与转速比 eta 的稳态工作点下，满电续航时间 T >= 4.0 h */
        attribute verifyMethod : String = "simulation";
        attribute priority : String = "high";
        attribute rationale : String = "任务剖面的巡航段占主要时长，单列为可验证条目。";
        attribute minEnduranceHours : Real = 4.0;
        // 追溯关系 (relations):
        //   REQ-CRUISE-ENDURANCE --refines--> REQ-MISSION-ENDURANCE  (由任务级续航需求分解而来)
        //   REQ-CRUISE-ENDURANCE --satisfiedBy--> PART-BATTERY-PACK  (由电池包可用能量与放电效率保障)
    }
    // id: REQ-MISSION-ENDURANCE
    requirement def MissionEndurance {
        doc /* 任务级续航：共轴八旋翼须按指定任务剖面完成起飞、巡航与安全返航。 */
        doc /* 验收判据: 在标称任务剖面（含 0.5 h 裕度）下，全程可用飞行时间 T_mission >= 5.0 h，且降落时电池剩余电量 >= 15%。 */
        attribute verifyMethod : String = "simulation";
        attribute priority : String = "high";
        attribute rationale : String = "任务书对滞空时长的总体要求，是下层续航需求的分解源头。";
        attribute minLandingReserveFraction : Real = 0.15;
        attribute minMissionDurationHours : Real = 5.0;
        // 追溯关系 (relations):
        //   REQ-MISSION-ENDURANCE --decomposes--> REQ-CRUISE-ENDURANCE  (任务级续航分解为巡航段的续航需求)
        //   REQ-MISSION-ENDURANCE --satisfiedBy--> PART-POWER-CHAIN  (由功率链（电池→电调→电机→桨）的整体能量效率保障)
    }
    // id: REQ-POWER-BUDGET
    requirement def CruisePowerBudget {
        doc /* 巡航稳态下整机电功率不超过电池可持续放电功率上限。 */
        doc /* 验收判据: P_cruise <= 0.9 * P_batt_max，其中 P_batt_max 为电池包持续放电功率额定值。 */
        attribute verifyMethod : String = "analysis";
        attribute priority : String = "medium";
        attribute rationale : String = "功率超限会同时破坏续航与电池寿命。";
        attribute batteryDeratingFactor : Real = 0.9;
        attribute maxCruisePowerW : Real = 260.0;
        // 追溯关系 (relations):
        //   REQ-POWER-BUDGET --refines--> REQ-CRUISE-ENDURANCE  (功率预算是续航指标的能量侧约束)
        //   REQ-POWER-BUDGET --satisfiedBy--> PART-POWER-CHAIN  (由功率链各环节的效率与选型共同保障)
    }
    // id: REQ-ROTOR-SPEED-RATIO
    requirement def RotorSpeedRatioBand {
        doc /* 在线寻优给出的上下桨转速比 eta 必须落在允许工作区间内。 */
        doc /* 验收判据: 对任意寻优输出满足 0.75 <= eta <= 1.25；且任一时刻任一桨的转速不超过其额定上限。 */
        attribute verifyMethod : String = "simulation";
        attribute priority : String = "high";
        attribute rationale : String = "转速比过小或过大会使共轴双桨进入气动干涉区，效率骤降并加剧振动。";
        attribute maxRotorSpeedRpm : Real = 6200.0;
        attribute maxSpeedRatio : Real = 1.25;
        attribute minSpeedRatio : Real = 0.75;
        // 追溯关系 (relations):
        //   REQ-ROTOR-SPEED-RATIO --refines--> REQ-CRUISE-ENDURANCE  (转速比区间是达成巡航续航的技术手段约束)
        //   REQ-ROTOR-SPEED-RATIO --satisfiedBy--> ACT-ONLINE-OPTIMIZATION  (由在线功率优化功能在寻优时施加区间约束)
    }

    // ---- ActionDefinition ----
    // id: ACT-ONLINE-OPTIMIZATION
    // description: 在线功率优化：边飞边算，实时求解使 P_cruise 最小的 (v, eta)，并把转速比约束在允许区间内。
    action def OnlinePowerOptimization {
        in powerTelemetry : Real;  // unit: W
        in airspeedEstimate : Real;  // unit: m/s
        out speedRatioEta : Real;
        out cruiseSpeed : Real;  // unit: m/s
        // 追溯关系 (relations):
        //   ACT-ONLINE-OPTIMIZATION --verifies--> REQ-ROTOR-SPEED-RATIO  (仿真中校验寻优输出始终落在 [0.75, 1.25])
        //   ACT-ONLINE-OPTIMIZATION --decomposes--> ACT-SIM-ENDURANCE  (在线优化的寻优结果交由续航仿真工况评价)
    }
    // id: ACT-SIM-ENDURANCE
    // description: 续航仿真工况：在给定 v 与 eta 的稳态工作点上跑能耗模型，输出续航时间。
    action def EnduranceSimulationRun {
        in cruiseSpeed : Real;  // unit: m/s
        in speedRatioEta : Real;
        out enduranceHours : Real;  // unit: h
        // 追溯关系 (relations):
        //   ACT-SIM-ENDURANCE --verifies--> REQ-CRUISE-ENDURANCE  (该仿真工况直接验证巡航续航指标)
        //   ACT-SIM-ENDURANCE --verifies--> REQ-MISSION-ENDURANCE  (任务剖面续航同样由该仿真工况给出)
        //   ACT-SIM-ENDURANCE --verifies--> REQ-POWER-BUDGET  (同一仿真同时输出稳态电功率，用于核对功率预算)
    }

    // ---- StateDefinition ----
    // id: STATE-FLIGHT-MODES
    // description: 飞行模式状态机：初始态为起飞段，起飞爬升完成（完成迁移，不挂 trigger/guard）后转入巡航；巡航可被返航指令或转速比越界事件打断；返航与故障两条路径都以触地检测收束到降落完成态。guard 里的 0.75 是占位阈值（对应 REQ-ROTOR-SPEED-RATIO 的下限），非实测结论。
    state def FlightModeStates {
        entry; then Takeoff;
        state Takeoff;
        state Cruise;
        state ReturnToHome;
        state Fault;
        state Landed;
        transition Transition_Takeoff_to_Cruise_0 first Takeoff then Cruise;
        // trigger: 返航指令或任务段剩余时间不足
        transition Transition_Cruise_to_ReturnToHome_1 first Cruise then ReturnToHome;
        // trigger: 转速比越界或功率遥测持续异常
        transition Transition_Cruise_to_Fault_2 first Cruise if (x8System.speedRatioEta <= 0.75) then Fault;
        // trigger: 触地检测（起落架受压）
        transition Transition_ReturnToHome_to_Landed_3 first ReturnToHome then Landed;
        // trigger: 迫降完成（触地检测）
        transition Transition_Fault_to_Landed_4 first Fault then Landed;
    }

}

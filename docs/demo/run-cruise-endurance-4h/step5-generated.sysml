// Generated by sysml-modeling-agent - schema sysml-ir/v1.
// Source of truth is the IR JSON; regenerate with generate_sysml. Do not edit by hand.
package CoaxialOctoRotor {

    // ---- PartDefinition ----
    // description: 功率链：电池 → 电调 → 电机 → 桨。
    part def PowerChain;

    // ---- PartUsage ----
    part powerChain : PowerChain;

    // ---- Requirement ----
    requirement def CruiseEndurance {
        doc /* 巡航时间不低于 4 小时 */
        doc /* 验收判据: 在巡航速度 v 与转速比 eta 的稳态工作点下，满电续航时间 T >= 4.0 h */
        attribute verifyMethod : String = "simulation";
        attribute minEnduranceHours : Real = 4.0;
        // 追溯关系 (relations):
        //   REQ-CRUISE-ENDURANCE --refines--> REQ-MISSION-ENDURANCE  (由任务级续航需求分解而来：巡航段是任务剖面中耗时最长的一段)
        //   REQ-CRUISE-ENDURANCE --satisfiedBy--> PART-POWER-CHAIN  (由功率链（电池→电调→电机→桨）的设计参数保障)
    }
    requirement def MissionEndurance {
        doc /* 任务级续航：共轴八旋翼须按指定任务剖面完成起飞、巡航与安全返航。 */
        doc /* 验收判据: 在标称任务剖面下，全程可用飞行时间 T_mission >= 5.0 h。 */
        attribute verifyMethod : String = "simulation";
        attribute minMissionDurationHours : Real = 5.0;
        // 追溯关系 (relations):
        //   REQ-MISSION-ENDURANCE --satisfiedBy--> PART-POWER-CHAIN  (由功率链的整体能量效率保障)
    }

    // ---- ActionDefinition ----
    // description: 续航仿真工况。
    action def EnduranceSimulationRun {
        in cruiseSpeed : Real;  // unit: m/s
        out enduranceHours : Real;  // unit: h
        // 追溯关系 (relations):
        //   ACT-SIM-ENDURANCE --verifies--> REQ-MISSION-ENDURANCE  (该仿真工况验证任务级续航)
        //   ACT-SIM-ENDURANCE --verifies--> REQ-CRUISE-ENDURANCE  (同一仿真工况直接验证巡航续航指标)
    }

}
